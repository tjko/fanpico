FanPico-MIB DEFINITIONS ::= BEGIN

IMPORTS
    MODULE-IDENTITY, OBJECT-TYPE, enterprises
        FROM SNMPv2-SMI;

fanpico MODULE-IDENTITY
    LAST-UPDATED "202501010000Z"
    ORGANIZATION "TJKO Industries"
    CONTACT-INFO
	"Timo Kokkonen
	EMail: tjko@iki.fi
        https://kokkonen.net/fanpico/"

    DESCRIPTION
	"The MIB module for FanPico Smart PWM (PC) Fan Controllers."

    REVISION  "202501010000Z"
    DESCRIPTION "Initial revision of this MIB module."

    ::= { enterprises 63264 1 42 }



fanCount OBJECT-TYPE
	SYNTAX		INTEGER (0..255)
	MAX-ACCESS	read-only
	STATUS		current
	DESCRIPTION
		"Number of Fan (output) ports present on the device."
	::= { fanpico 1 }

fanTable OBJECT-TYPE
	SYNTAX		SEQUENCE OF fanTableEntry
	MAX-ACCESS     	not-accessible
	STATUS         	current
	DESCRIPTION
		"This table contains current Fan statuses."
	::= { fanpico 2 }

fanTableEntry OBJECT-TYPE
	SYNTAX		fanEntry
	MAX-ACCESS	not-accessible
	STATUS		current
	DESCRIPTION
		"Fan status table entry."
	INDEX { fanID }
	::= { fanTable 1 }

fanEntry ::= SEQUENCE {
	 fanID		INTEGER,
	 fanName	OCTET STRING,
	 fanRPM		INTEGER,
	 fanFrequency   INTEGER,
	 fanDutyCycle	INTEGER
	 }

fanID OBJECT-TYPE
	SYNTAX		INTEGER (1..255)
	MAX-ACCESS	read-only
	STATUS		current
	DESCRIPTION
		"Fan port number."
	::= { fanTableEntry 1 }

fanName OBJECT-TYPE
	SYNTAX		OCTET STRING
	MAX-ACCESS	read-only
	STATUS		current
	DESCRIPTION
		"Fan port name."
	::= { fanTableEntry 2 }

fanRPM OBJECT-TYPE
	SYNTAX		INTEGER (0..100000)
	MAX-ACCESS	read-only
	STATUS		current
	DESCRIPTION
		"Fan RPM."
	::= { fanTableEntry 3 }

fanFrequency OBJECT-TYPE
	SYNTAX		INTEGER (0..100000)
	MAX-ACCESS	read-only
	STATUS		current
	DESCRIPTION
		"Fan tachometer signal frequency."
	::= { fanTableEntry 4 }

fanDutyCycle OBJECT-TYPE
	SYNTAX		INTEGER (0..100)
	MAX-ACCESS	read-only
	STATUS		current
	DESCRIPTION
		"Fan PWM signal duty cycle."
	::= { fanTableEntry 5 }

mbfanCount OBJECT-TYPE
	SYNTAX		INTEGER (0..255)
	MAX-ACCESS	read-only
	STATUS		current
	DESCRIPTION
		"Number of MB Fan (input) ports present on the device."
	::= { fanpico 3 }

sensorCount OBJECT-TYPE
	SYNTAX		INTEGER (0..255)
	MAX-ACCESS	read-only
	STATUS		current
	DESCRIPTION
		"Number of analog sensor ports present on the device."
	::= { fanpico 5 }


END
